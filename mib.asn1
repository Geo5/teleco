Agent-MIB DEFINITIONS ::= BEGIN

IMPORTS
    OBJECT-TYPE, IpAddress FROM SNMPv2-SMI;

agent OBJECT IDENTIFIER ::= { 1 3 6 1 3 }

Entered OBJECT-TYPE
    SYNTAX INTEGER
    MAX-ACCESS read-write
    STATUS current
    DESCRIPTON "Number of people which entered"
    ::= { agent 1 }

Left OBJECT-TYPE
    SYNTAX INTEGER
    MAX-ACCESS read-write
    STATUS current
    DESCRIPTON "Number of people which left"
    ::= { agent 2 }

DeviceIP OBJECT-TYPE
    SYNTAX IpAddress
    MAX-ACCESS read-write
    STATUS current
    DESCRIPTON "Device IP address"
    ::= { agent 3 }


HistoryEntry ::= SEQUENCE {
   DayOfYear INTEGER (1..365)
   Entered INTEGER
   Left INTEGER
}


History OBJECT-TYPE
    SYNTAX SEQUENCE OF HistoryEntry
    MAX-ACCESS read-write
    STATUS current
    DESCRIPTON "Device IP address"
    ::= { agent 4 }

END
